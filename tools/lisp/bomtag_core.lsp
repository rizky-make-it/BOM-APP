;;; BOMTAG v2 - Tala BOM-APP. Commands: BOMTAG (tag a component), BOMCHECK (audit tags), BOMEXPORT (JSON for BOM-APP).
;;; v2: every prompt arrives PRE-FILLED. The part under the click is identified from (1) the drafter's own label whose arrow lands there (LEADER+MTEXT or MULTILEADER),
;;; (2) Part Master v3 names/aliases, (3) Part Master default material code (thickness follows it), (4) the measured face. The drafter presses Enter to accept or types to override.
;;; Tag = boxed number + leader (layer BOM-NO). Data lives in XDATA (app TALA_BOM) on the number text.
(setq *bt-app* "TALA_BOM" *bt-layer* "BOM-NO" *bt-last* (list "" "A" 1 18.0) *bt-col* 5)
(defun bt-regapp () (if (not (tblsearch "APPID" *bt-app*)) (regapp *bt-app*)))
(defun bt-mklayer (nm col)
  (if (not (tblsearch "LAYER" nm))
    (entmake (list '(0 . "LAYER") '(100 . "AcDbSymbolTableRecord") '(100 . "AcDbLayerTableRecord") (cons 2 nm) '(70 . 0) (cons 62 col) '(6 . "Continuous")))))
(defun bt-lay () (bt-mklayer *bt-layer* 5) (bt-mklayer "BOM-DONE" 3) (bt-mklayer "BOM-CHECK" 2) (bt-mklayer "BOM-TODO" 1))
(defun bt-name (no / a) (setq a (assoc no *bt-parts*)) (if a (cadr a) ""))
(defun bt-pmcode (no / a) (setq a (assoc no *bt-pm*)) (if a (caddr a) ""))
(defun bt-mat-ok (c) (or (member c *bt-mats*) (and (> (strlen c) 3) (= (substr c 1 3) "MT-"))))
(defun bt-panel-code-p (c) (and (> (strlen c) 1) (member (substr c 1 2) '("B-" "C-"))))
(defun bt-code-t (c / s p) (setq s (substr c 3) p (vl-string-search "-" s)) (if p (atof (substr s 1 p)) 0.0))
(defun bt-xd (e / d x) (setq d (entget e (list *bt-app*)) x (assoc -3 d)) (if x (mapcar 'cdr (cdr (cadr x)))))
(defun bt-nrm () (trans '(0.0 0.0 1.0) 1 0 T))
(defun bt-ln (a b) (entmake (list '(0 . "LINE") (cons 8 *bt-layer*) (cons 62 *bt-col*) (cons 10 (trans a 1 0)) (cons 11 (trans b 1 0)))))
(defun bt-js (s / o i c k) (setq o "" i 1)
  (while (<= i (strlen s)) (setq c (substr s i 1) k (ascii c))
    (cond ((= k 34) (setq o (strcat o "'"))) ((= k 92) (setq o (strcat o "/"))) ((< k 32) (setq o (strcat o " "))) (t (setq o (strcat o c))))
    (setq i (1+ i))) o)
(defun bt-tags (/ e r f) (setq e (entnext) r '())
  (while e (setq f (bt-xd e)) (if (and f (>= (length f) 12)) (setq r (cons (append f (list (cdr (assoc 210 (entget e))))) r))) (setq e (entnext e))) (reverse r))
(defun bt-next-row (/ mx f) (setq mx 0) (foreach f (bt-tags) (setq mx (max mx (atoi (car f))))) (1+ mx))
(defun bt-spec (no l w tt code) (strcat no "|" (rtos l 2 1) "|" (rtos w 2 1) "|" (rtos tt 2 1) "|" code))
(defun bt-find (spec / hit f) (foreach f (bt-tags) (if (and (not hit) (= spec (bt-spec (nth 1 f) (atof (nth 3 f)) (atof (nth 4 f)) (atof (nth 5 f)) (nth 7 f)))) (setq hit f))) hit)

;; ---------------- auto-fill: read the drafter's labels
(defun bt-clean (s / o i c n j nx) (setq o "" i 1 n (strlen s))
  (while (<= i n)
    (setq c (substr s i 1))
    (cond ((or (= c "{") (= c "}")) nil)
          ((= c "\\")
           (setq nx (strcase (substr s (1+ i) 1)))
           (cond ((and (= nx "P") (= (strcase (substr s (+ i 2) 1)) "X")) (setq j (vl-string-search ";" s i)) (if j (setq i (1+ j)) (setq i (1+ i))))
                 ((= nx "P") (setq o (strcat o " ") i (1+ i)))
                 ((member nx '("L" "O" "K")) (setq i (1+ i)))
                 (T (setq j (vl-string-search ";" s i)) (if (and j (< (- j i) 40)) (setq i (1+ j)) (setq i (1+ i))))))
          (T (setq o (strcat o c))))
    (setq i (1+ i)))
  o)
(defun bt-mt-list (/ ss i r d) (setq r '() ss (ssget "_X" '((0 . "MTEXT,TEXT") (410 . "Model"))))
  (if ss (progn (setq i 0) (while (< i (sslength ss)) (setq d (entget (ssname ss i)) r (cons (list (cdr (assoc 10 d)) (bt-clean (cdr (assoc 1 d)))) r) i (1+ i))))) r)
(defun bt-nearest-text (pt tl / best bd d a) (setq best "")
  (foreach a tl (setq d (distance pt (car a))) (if (or (not bd) (< d bd)) (setq bd d best (cadr a))))
  (if (and bd (< bd 900.0)) best ""))
(defun bt-mleader (d / txt tip sect stack v a) (setq sect "" stack '() tip '(0 0 0) txt "")
  (foreach a d (setq v (cdr a))
    (cond ((and (member (car a) '(300 302 304)) (= (type v) 'STR) (wcmatch v "*{")) (setq stack (cons v stack) sect v))
          ((and (member (car a) '(301 303)) (= (type v) 'STR) (= v "}")) (setq stack (cdr stack) sect (if stack (car stack) "")))
          ((and (= (car a) 304) (= sect "CONTEXT_DATA{")) (setq txt v))
          ((and (= (car a) 10) (= sect "LEADER_LINE{") (equal tip '(0 0 0))) (setq tip v))))
  (list tip (bt-clean txt)))
(defun bt-labels (/ tl out ss i d vs a)
  (setq tl (bt-mt-list) out '())
  (setq ss (ssget "_X" '((0 . "LEADER") (410 . "Model"))))
  (if ss (progn (setq i 0)
    (while (< i (sslength ss))
      (setq d (entget (ssname ss i)) vs '())
      (foreach a d (if (= (car a) 10) (setq vs (append vs (list (cdr a))))))
      (if vs (setq out (cons (list (car vs) (bt-nearest-text (last vs) tl)) out)))
      (setq i (1+ i)))))
  (setq ss (ssget "_X" '((0 . "MULTILEADER") (410 . "Model"))))
  (if ss (progn (setq i 0)
    (while (< i (sslength ss)) (setq out (cons (bt-mleader (entget (ssname ss i))) out)) (setq i (1+ i)))))
  out)
(defun bt-near-label (pcw / best bd d a)
  (foreach a (bt-labels)
    (if (/= (cadr a) "") (progn (setq d (distance pcw (car a))) (if (or (not bd) (< d bd)) (setq bd d best a)))))
  (if (and bd (<= bd 300.0)) best nil))
(defun bt-kwmatch (txt / best bl k)
  (setq bl 0)
  (foreach k *bt-kw* (if (and (> (strlen (car k)) bl) (wcmatch txt (strcat "*" (car k) "*"))) (setq bl (strlen (car k)) best (cadr k))))
  (if best best ""))
(defun bt-std-t (m / best bd s) (setq bd 1e9)
  (foreach s '(6 9 12 15 18 25) (if (< (abs (- s m)) bd) (setq bd (abs (- s m)) best s)))
  (if (<= bd 3.0) (float best) nil))
(defun bt-txt-t (txt / r s) (setq r nil)
  (foreach s '(25 18 15 12 9 6) (if (and (not r) (wcmatch txt (strcat "*" (itoa s) "MM*"))) (setq r (float s)))) r)
(defun bt-metal-code (txt / r c) (setq r nil)
  (foreach c *bt-mats* (if (and (not r) (> (strlen c) 3) (= (substr c 1 3) "MT-") (wcmatch txt (strcat "*" (strcase (substr c 4)) "*"))) (setq r c))) r)
;; -> (part_no material_code thickness source label_text)   pcw = click in WCS, l/w = measured long/short side
(defun bt-suggest (pcw l w / lab txt no pmc fam code tt faces src)
  (setq lab (bt-near-label pcw) txt (if lab (strcase (cadr lab)) "")
        no (if lab (bt-kwmatch txt) "") pmc (if (/= no "") (bt-pmcode no) "")
        fam (cond ((wcmatch txt "*PLYWOOD*,*PLY *,*PLY") "B") ((wcmatch txt "*MDF*") "C") ((wcmatch txt "*SOLID*,*WOOD*") "A") (T ""))
        tt (bt-txt-t txt) src (if lab (strcat "label '" (cadr lab) "'") "tidak ada label di titik ini"))
  (cond ((bt-metal-code txt) (setq code (bt-metal-code txt)))
        ((member fam '("B" "C"))
         (setq faces (if (bt-panel-code-p pmc) (substr pmc 6) "1X"))
         (if (not tt) (setq tt (if (bt-panel-code-p pmc) (bt-code-t pmc) (bt-std-t w))))
         (if (not tt) (setq tt 18.0))
         (setq code (strcat fam "-" (itoa (fix tt)) "-" faces)))
        ((= fam "A") (setq code "A"))
        ((/= pmc "") (setq code pmc))
        (T (setq code "")))
  (if (and (/= no "") (= fam "") (/= pmc "")) (setq src (strcat src " + Part Master")))
  (if (not tt) (setq tt (if (bt-panel-code-p code) (bt-code-t code) 0.0)))
  (list no code (float tt) src (if lab (cadr lab) "")))

;; ---------------- core (no user input): tip/box are UCS points. Returns STATED or CHECK.
(defun bt-add (row no l w tt qty code tip box h / hs cx cy cz n nm st x1 x2 y1 y2 ex ey tw fld bb cs)
  (bt-regapp) (bt-lay)
  (setq hs (* 1.1 h) cx (car box) cy (cadr box) cz (if (caddr box) (caddr box) 0.0) n (bt-nrm) nm (bt-name no)
        st (if (and (/= nm "") (bt-mat-ok code) (> l 0) (> w 0)
                    (not (and (bt-panel-code-p code) (< (min l w) (* 3.0 tt))))) "STATED" "CHECK")
        x1 (- cx hs) x2 (+ cx hs) y1 (- cy hs) y2 (+ cy hs) tip (list (car tip) (cadr tip) (if (caddr tip) (caddr tip) 0.0)))
  (setq *bt-col* (if (= st "STATED") 3 2))
  (if (>= (abs (- (car tip) cx)) (abs (- (cadr tip) cy)))
    (setq ex (if (> (car tip) cx) x2 x1) ey cy)
    (setq ex cx ey (if (> (cadr tip) cy) y2 y1)))
  (bt-ln (list x1 y1 cz) (list x2 y1 cz)) (bt-ln (list x2 y1 cz) (list x2 y2 cz)) (bt-ln (list x2 y2 cz) (list x1 y2 cz)) (bt-ln (list x1 y2 cz) (list x1 y1 cz))
  (bt-ln tip (list ex ey cz))
  (setq bb (if *bt-box* *bt-box* (list (- (car tip) (/ l 2.0)) (- (cadr tip) (/ w 2.0)) (+ (car tip) (/ l 2.0)) (+ (cadr tip) (/ w 2.0)) (caddr tip)))
        cs (list (list (nth 0 bb) (nth 1 bb) (nth 4 bb)) (list (nth 2 bb) (nth 1 bb) (nth 4 bb)) (list (nth 2 bb) (nth 3 bb) (nth 4 bb)) (list (nth 0 bb) (nth 3 bb) (nth 4 bb)))
        *bt-box* nil
        tw (trans tip 1 0)
        fld (append (list (itoa row) no nm (rtos l 2 2) (rtos w 2 2) (rtos tt 2 2) (itoa qty) code st (rtos (car tw) 2 3) (rtos (cadr tw) 2 3) (rtos (caddr tw) 2 3))
                    (apply 'append (mapcar '(lambda (c / p) (setq p (trans c 1 0)) (list (rtos (car p) 2 3) (rtos (cadr p) 2 3) (rtos (caddr p) 2 3))) cs))))
  (entmake (list '(0 . "TEXT") (cons 8 *bt-layer*) (cons 62 *bt-col*) (cons 10 (trans (list cx cy cz) 1 n)) (cons 40 (* 0.9 h)) (cons 1 (itoa row)) '(72 . 1) '(73 . 2)
                 (cons 11 (trans (list cx cy cz) 1 n)) (cons 210 n) (list -3 (cons *bt-app* (mapcar '(lambda (s) (cons 1000 s)) fld)))))
  (bt-mark-box (mapcar '(lambda (c) (trans c 1 0)) cs) st n)
  st)
(defun bt-export (path / fl first f tg)
  (setq fl (open path "w") tg (bt-tags) first T)
  (write-line "{\"tags\":[" fl)
  (foreach f tg
    (write-line (strcat (if first "" ",") "{\"row\":" (nth 0 f) ",\"part_no\":\"" (bt-js (nth 1 f)) "\",\"name\":\"" (bt-js (nth 2 f)) "\",\"l\":" (nth 3 f) ",\"w\":" (nth 4 f) ",\"t\":" (nth 5 f)
                        ",\"qty\":" (nth 6 f) ",\"code\":\"" (bt-js (nth 7 f)) "\",\"status\":\"" (nth 8 f) "\",\"tip\":[" (nth 9 f) "," (nth 10 f) "," (nth 11 f) "]}") fl)
    (setq first nil))
  (write-line "]}" fl) (close fl) (length tg))
(defun bt-check (/ tg msgs seen f r sp old m)
  (setq tg (bt-tags) msgs '() seen '())
  (foreach f tg
    (setq r (car f) sp (bt-spec (nth 1 f) (atof (nth 3 f)) (atof (nth 4 f)) (atof (nth 5 f)) (nth 7 f)))
    (if (= (bt-name (nth 1 f)) "") (setq msgs (cons (strcat "tag " r ": nomor part '" (nth 1 f) "' tidak ada di Part Master v3") msgs)))
    (if (not (bt-mat-ok (nth 7 f))) (setq msgs (cons (strcat "tag " r ": kode bahan '" (nth 7 f) "' tidak dikenal") msgs)))
    (if (or (<= (atof (nth 3 f)) 0) (<= (atof (nth 4 f)) 0)) (setq msgs (cons (strcat "tag " r ": ukuran L/W belum terisi") msgs)))
    (if (and (bt-panel-code-p (nth 7 f)) (> (atof (nth 4 f)) 0) (< (min (atof (nth 3 f)) (atof (nth 4 f))) (* 3.0 (atof (nth 5 f)))))
      (setq msgs (cons (strcat "tag " r ": lebar " (nth 4 f) " terlalu kecil untuk panel " (nth 5 f) " mm (tampak samping/tepi?)") msgs)))
    (setq old (assoc r seen))
    (if (and old (/= (cdr old) sp)) (setq msgs (cons (strcat "nomor " r " dipakai untuk 2 spesifikasi berbeda") msgs)))
    (if (not old) (setq seen (cons (cons r sp) seen))))
  (princ (strcat "\nBOMCHECK: " (itoa (length tg)) " tag, " (itoa (length seen)) " baris unik, " (itoa (length msgs)) " masalah"))
  (foreach m (reverse msgs) (princ (strcat "\n  - " m)))
  (length msgs))

;; ---------------- interactive commands (need a person; NOT exercised by the headless test)
(defun bt-ask-part (def / s ok p)
  (setq ok nil)
  (while (not ok)
    (setq s (getstring (strcat "\nNo part Part Master v3, ? = daftar <" def ">: ")))
    (cond ((= s "") (setq s def) (setq ok (/= (bt-name s) "")) (if (not ok) (princ "\n  isi nomor part dulu (ketik ? untuk daftar)")))
          ((= s "?") (foreach p *bt-parts* (princ (strcat "\n  " (car p) "  " (cadr p)))))
          ((/= (bt-name s) "") (setq ok T))
          (T (princ "\n  nomor tidak ada di Part Master v3"))))
  s)
(defun c:BOMTAG (/ h pt pcw bx no code qty l w tt hit row s1 s2 e0 bnd d xs ys zs pu a sg ld st)
  (bt-regapp) (bt-lay)
  (setq h (* 0.02 (getvar "VIEWSIZE")))
  (command "_.UCS" "_V")
  (while (setq pt (getpoint "\nKlik di dalam komponen (Enter = selesai): "))
    (setq l 0.0 w 0.0 e0 (entlast) bnd nil pcw (trans pt 1 0) *bt-box* nil)
    (command "_.-BOUNDARY" pt "")
    (if (and (entlast) (not (equal (entlast) e0)))
      (progn (setq bnd (entlast) d (entget bnd) xs '() ys '() zs 0.0)
             (foreach a d (if (= (car a) 10)
                            (progn (setq pu (trans (list (cadr a) (caddr a) (if (assoc 38 d) (cdr (assoc 38 d)) 0.0)) (cdr (assoc 210 d)) 1))
                                   (setq xs (cons (car pu) xs) ys (cons (cadr pu) ys) zs (caddr pu)))))
             (if xs (setq l (max (- (apply 'max xs) (apply 'min xs)) (- (apply 'max ys) (apply 'min ys))) w (min (- (apply 'max xs) (apply 'min xs)) (- (apply 'max ys) (apply 'min ys)))
                          *bt-box* (list (apply 'min xs) (apply 'min ys) (apply 'max xs) (apply 'max ys) zs)))
             (entmod (append d (list (cons 62 1)))) (entupd bnd)))
    (princ (strcat "\nBidang merah terukur: " (rtos l 2 1) " x " (rtos w 2 1) " mm"))
    (setq sg (bt-suggest pcw l w) ld (if (/= (car sg) "") (car sg) (car *bt-last*)))
    (princ (strcat "\nSARAN: " (if (/= (car sg) "") (strcat (car sg) " " (bt-name (car sg))) "(nama part belum bisa ditebak)") "  bahan " (if (/= (cadr sg) "") (cadr sg) "?") "  <- " (cadddr sg)))
    (setq no (bt-ask-part ld))
    (princ (strcat "  -> " (bt-name no)))
    (setq ld (cadr sg))
    (if (and (/= (car sg) "") (/= no (car sg))) (setq ld (bt-pmcode no)))
    (if (and (= (car sg) "") (= ld "")) (setq ld (bt-pmcode no)))
    (setq code "")
    (while (= code "")
      (setq code (getstring (strcat "\nKode bahan (A, A1, B-18-1X, C-18-1X, MT-20x20, ...)" (if (/= ld "") (strcat " <" ld ">") " (WAJIB diisi, tidak ada saran)") ": ")))
      (if (and (= code "") (/= ld "")) (setq code ld)))
    (setq s1 (getreal (strcat "\nPanjang <" (rtos l 2 1) ">: "))) (if s1 (setq l s1))
    (setq s2 (getreal (strcat "\nLebar <" (rtos w 2 1) ">: "))) (if s2 (setq w s2))
    (setq tt (caddr sg))
    (if (bt-panel-code-p code) (setq tt (bt-code-t code)))
    (setq s1 (getreal (strcat "\nTebal" (if (> tt 0) (strcat " <" (rtos tt 2 1) ">") " (WAJIB, tidak terbaca di gambar)") ": ")))
    (if s1 (setq tt s1))
    (while (<= tt 0) (setq tt (getreal "\nTebal (mm) wajib diisi: ")) (if (not tt) (setq tt 0)))
    (setq hit (bt-find (bt-spec no l w tt code)))
    (if hit
      (setq row (atoi (car hit)) qty (atoi (nth 6 hit)))
      (progn (setq row (bt-next-row)) (setq qty (getint (strcat "\nJumlah total part ini <" (itoa (nth 2 *bt-last*)) ">: "))) (if (not qty) (setq qty (nth 2 *bt-last*)))))
    (setq bx (getpoint pt "\nTitik kotak nomor: "))
    (if bx (progn (setq st (bt-add row no l w tt qty code pt bx h))
                  (princ (strcat "\nTag " (itoa row) ": " st (if (= st "STATED") "  (bidang HIJAU = sudah ditandai)" "  (bidang KUNING = perlu dicek)")))))
    (if bnd (entdel bnd))
    (setq *bt-last* (list no code qty tt)))
  (command "_.UCS" "_P")
  (princ))
;; ---------------- visible progress: green fill = tagged (STATED), yellow = tagged but CHECK, red circle = drafter label with NO tag yet
;; The filled box is a transparent SOLID built from the face box stored in the tag (no HATCH: it fails on faces that are not perfectly closed).
(defun bt-mark-box (cs st n / c4 lay)
  (bt-lay)
  (setq lay (if (= st "STATED") "BOM-DONE" "BOM-CHECK") c4 (mapcar '(lambda (p) (trans p 0 n)) cs))
  (entmake (list '(0 . "SOLID") (cons 8 lay) (cons 10 (nth 0 c4)) (cons 11 (nth 1 c4)) (cons 12 (nth 3 c4)) (cons 13 (nth 2 c4)) (cons 210 n) (cons 440 (+ 33554432 100))))
  T)
(defun bt-p (f i) (list (atof (nth i f)) (atof (nth (+ i 1) f)) (atof (nth (+ i 2) f))))
(defun bt-mark-tag (f) (if (>= (length f) 25) (bt-mark-box (list (bt-p f 12) (bt-p f 15) (bt-p f 18) (bt-p f 21)) (nth 8 f) (last f)) nil))
(defun bt-clear (/ l ss i)
  (foreach l '("BOM-DONE" "BOM-CHECK" "BOM-TODO")
    (setq ss (ssget "_X" (list (cons 8 l))))
    (if ss (progn (setq i 0) (while (< i (sslength ss)) (entdel (ssname ss i)) (setq i (1+ i)))))))
(defun bt-tip (f) (list (atof (nth 9 f)) (atof (nth 10 f)) (atof (nth 11 f))))
(defun bt-covered (p tg / hit f n q xs ys)
  (foreach f tg
    (if (< (distance p (bt-tip f)) 250.0) (setq hit T))
    (if (and (not hit) (>= (length f) 25))
      (progn (setq n (last f) q (trans p 0 n)
                   xs (mapcar '(lambda (i) (car (trans (bt-p f i) 0 n))) '(12 15 18 21))
                   ys (mapcar '(lambda (i) (cadr (trans (bt-p f i) 0 n))) '(12 15 18 21)))
             (if (and (>= (car q) (- (apply 'min xs) 1.0)) (<= (car q) (+ (apply 'max xs) 1.0)) (>= (cadr q) (- (apply 'min ys) 1.0)) (<= (cadr q) (+ (apply 'max ys) 1.0))) (setq hit T)))))
  hit)
(defun bt-show (/ tg f lb n-done n-todo h n)
  (bt-lay) (bt-clear)
  (setq tg (bt-tags) n-done 0 n-todo 0 h (* 0.02 (getvar "VIEWSIZE")) n (bt-nrm))
  (foreach f tg (if (bt-mark-tag f) (setq n-done (1+ n-done))))
  (foreach lb (bt-labels)
    (if (and (/= (cadr lb) "") (not (bt-covered (car lb) tg)))
      (progn (setq n-todo (1+ n-todo))
             (entmake (list '(0 . "CIRCLE") (cons 8 "BOM-TODO") '(62 . 1) (cons 10 (trans (car lb) 0 n)) (cons 40 (min (* 1.5 h) 45.0)) (cons 210 n))))))
  (princ (strcat "\nBOMSHOW: " (itoa n-done) " bidang diwarnai (hijau = STATED, kuning = CHECK); " (itoa n-todo) " label drafter BELUM ditandai (lingkaran MERAH)"))
  (list n-done n-todo))
(defun c:BOMSHOW () (command "_.UCS" "_V") (bt-show) (command "_.UCS" "_P") (princ))
(defun c:BOMCLEAR () (bt-clear) (princ "\nBOMCLEAR: warna/lingkaran dihapus (tag nomor tetap)") (princ))
(defun c:BOMCHECK () (bt-check) (princ))
(defun c:BOMEXPORT (/ p)
  (setq p (strcat (getvar "DWGPREFIX") (vl-filename-base (getvar "DWGNAME")) "_bomtag.json"))
  (princ (strcat "\n" (itoa (bt-export p)) " tag ditulis ke " p)) (bt-check) (princ))
(princ "\nBOMTAG v2 dimuat (isian otomatis): BOMTAG, BOMCHECK, BOMEXPORT")
(princ)
